;; Implementation file that defines the application commands.

(defun C:MyCommand1 ()
  (alert "Hello from MyCommand1!")
  (princ)
)

(defun C:MyCommand2 ()
  (alert "Hello from MyCommand2!")
  (princ)
)

(princ)

;;;-----BEGIN-SIGNATURE-----
;;; 5wUAADCCBeMGCSqGSIb3DQEHAqCCBdQwggXQAgEBMQ4wDAYIKoZIzj0EAwMFADAL
;;; BgkqhkiG9w0BBwGgggPAMIIDvDCCA0GgAwIBAgIQY41ujedUudgLItW1oB6uMTAK
;;; BggqhkjOPQQDAzB4MQswCQYDVQQGEwJVUzEOMAwGA1UECAwFVGV4YXMxEDAOBgNV
;;; BAcMB0hvdXN0b24xETAPBgNVBAoMCFNTTCBDb3JwMTQwMgYDVQQDDCtTU0wuY29t
;;; IENvZGUgU2lnbmluZyBJbnRlcm1lZGlhdGUgQ0EgRUNDIFIyMB4XDTI2MDcwNjE4
;;; NDAzM1oXDTI3MTAwNzE4NDAzM1owczELMAkGA1UEBhMCVVMxEDAOBgNVBAgMB0Zs
;;; b3JpZGExFjAUBgNVBAcMDUxhbmQgTycgTGFrZXMxETAPBgNVBAoMCE1BTlVTT0ZU
;;; MRQwEgYDVQQLDAtFbmdpbmVlcmluZzERMA8GA1UEAwwITUFOVVNPRlQwdjAQBgcq
;;; hkjOPQIBBgUrgQQAIgNiAAQZ5ODxAyLUuFHhL2bdROBWz+3Ha1J3AjxPD7sEGQgu
;;; 1bBIWMRiWXP9B2QKG/vAk3KvQZaOP32OoDSKihZriXdYbgXlt6FbMdPbxPUILmH7
;;; mp8/cJ0w8LC09T6sV6MLbmSjggGTMIIBjzAMBgNVHRMBAf8EAjAAMB8GA1UdIwQY
;;; MBaAFDJ4sQ6Q20bPGs+2YxFt/jDnZ1QwMHkGCCsGAQUFBwEBBG0wazBHBggrBgEF
;;; BQcwAoY7aHR0cDovL2NlcnQuc3NsLmNvbS9TU0xjb20tU3ViQ0EtY29kZVNpZ25p
;;; bmctRUNDLTM4NC1SMi5jZXIwIAYIKwYBBQUHMAGGFGh0dHA6Ly9vY3Nwcy5zc2wu
;;; Y29tMFEGA1UdIARKMEgwCAYGZ4EMAQQBMDwGDCsGAQQBgqkwAQMDATAsMCoGCCsG
;;; AQUFBwIBFh5odHRwczovL3d3dy5zc2wuY29tL3JlcG9zaXRvcnkwEwYDVR0lBAww
;;; CgYIKwYBBQUHAwMwTAYDVR0fBEUwQzBBoD+gPYY7aHR0cDovL2NybHMuc3NsLmNv
;;; bS9TU0xjb20tU3ViQ0EtY29kZVNpZ25pbmctRUNDLTM4NC1SMi5jcmwwHQYDVR0O
;;; BBYEFNHh1c+HWC/VnBp4XZMhy5YC4xaNMA4GA1UdDwEB/wQEAwIHgDAKBggqhkjO
;;; PQQDAwNpADBmAjEA34DOb5IC8XQzLF3kOM1S7qwsQn0dJQrtObv64Xf6v7fhj///
;;; SGPAqBMJUSyDiJR9AjEA+j21dj4t5AGd9vcAZLVxNcmtIDHkvfT+UhTab4fXLN2S
;;; FXxH/9OV25qUPWnSltoDMYIB6DCCAeQCAQEwgYwweDELMAkGA1UEBhMCVVMxDjAM
;;; BgNVBAgMBVRleGFzMRAwDgYDVQQHDAdIb3VzdG9uMREwDwYDVQQKDAhTU0wgQ29y
;;; cDE0MDIGA1UEAwwrU1NMLmNvbSBDb2RlIFNpZ25pbmcgSW50ZXJtZWRpYXRlIENB
;;; IEVDQyBSMgIQY41ujedUudgLItW1oB6uMTAMBggqhkjOPQQDAwUAMAsGByqGSM49
;;; AgEFAARoMGYCMQDK0mA1bh/b7fOo6JsTlo/soF8YuY4yQF3ZoiUMxl0Sho2Moeil
;;; NBJGRXNJ261s5fwCMQDlCt6nnzCAJo6XqSvy68Z/rTJINlZfGIUPh5vUdwI9Z+kQ
;;; 1RnQG2+Wz8BpqegaxuqhgcowgccGA1UdDjGBvwSBvDgAMwA7ADEAMAAvADIAMQAv
;;; ADIAMAAyADYALwAyAC8ANAA3AC8ANAA1AC8ATgBhAHQAaQBvAG4AYQBsACAASQBu
;;; AHMAdABpAHQAdQB0AGUAIABvAGYAIABTAHQAYQBuAGQAYQByAGQAcwAgAGEAbgBk
;;; ACAAVABlAGMAaABuAG8AbABvAGcAeQAgACgAdABpAG0AZQAtAGEALgBuAGkAcwB0
;;; AC4AZwBvAHYAKQBMAHMAcABMAG8AYQBkAAAA
;;; -----END-SIGNATURE-----
